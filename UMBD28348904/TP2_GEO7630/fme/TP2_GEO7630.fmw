FME workspace TP2_GEO7630.fmw

Parameters:
- SourceDataset_SHAPEFILE = https://donnees.montreal.ca/dataset/0eaea940-aafc-43bc-bab2-a87ac66a93ba/resource/c5dbe902-a587-4af5-ab97-d5182fa8ecba/download/affectationpu.zip   # Source Esri Shapefile(s)
- SourceDataset_SHAPEFILE_5 = https://donnees.montreal.ca/dataset/ead1ac6f-f37c-4326-a9b9-4508d94bbc45/resource/73d4571c-fd7a-465a-aa19-05c3b24222cc/download/hydrographie-2020.zip   # Source Esri Shapefile(s)
- SourceDataset_SHAPEFILE_7 = https://donnees.montreal.ca/dataset/c128aff5-325c-4599-ab66-1c9d0b3abc94/resource/a37e11d4-f0a3-46a7-8636-76754fad72b3/download/prmhh_courseau_fosses.zip   # Source Esri Shapefile(s)
- SourceDataset_GML_19 = https://donnees.montreal.ca/dataset/08a528e3-5bff-4bd8-b28d-85e584d5cc1d/resource/14ec49aa-7fad-4a9c-a3f0-3bf7322b8c1d/download/tin-2015-mercier-hochelaga-maisonneuve.zip   # Source Geography Markup Language (GML) File(s)
- SourceDataset_GML_16 = https://donnees.montreal.ca/dataset/08a528e3-5bff-4bd8-b28d-85e584d5cc1d/resource/adbd7f57-0e9a-4876-9e91-9624a56edbf4/download/tin-2015-pierrefonds-roxboro.zip   # Source Geography Markup Language (GML) File(s)
- SourceDataset_GML_20 = https://donnees.montreal.ca/dataset/08a528e3-5bff-4bd8-b28d-85e584d5cc1d/resource/0a9733fd-3508-477d-9152-502523551182/download/tin-2015-riviere-des-prairies-pointe-aux-trembles.zip   # Source Geography Markup Language (GML) File(s)
- SourceDataset_GML_12 = https://donnees.montreal.ca/dataset/08a528e3-5bff-4bd8-b28d-85e584d5cc1d/resource/50acb4b5-f0f2-4170-90fc-d51f7f2274e6/download/tin-2015-verdun.zip   # Source Geography Markup Language (GML) File(s)
- SourceDataset_GML_8 = https://donnees.montreal.ca/dataset/08a528e3-5bff-4bd8-b28d-85e584d5cc1d/resource/7ff01ab1-5b81-43ff-933a-e18402c8b5e6/download/tin-2015-ile-bizard-sainte-genevieve.zip   # Source Geography Markup Language (GML) File(s)
- SourceDataset_GML_7 = https://donnees.montreal.ca/dataset/08a528e3-5bff-4bd8-b28d-85e584d5cc1d/resource/022b28e5-9d4e-458e-af1f-e2efbc89b0bf/download/tin-2015-montreal-est.zip   # Source Geography Markup Language (GML) File(s)
- SourceDataset_GML = https://donnees.montreal.ca/dataset/08a528e3-5bff-4bd8-b28d-85e584d5cc1d/resource/821302a3-1ac9-4cf4-8309-0e7bc07fb843/download/tin-2015-ahuntsic-cartierville.zip   # Source Geography Markup Language (GML) File(s)
- SourceDataset_XML = https://donnees.montreal.ca/dataset/08a528e3-5bff-4bd8-b28d-85e584d5cc1d/resource/3b22f8f4-a5e3-4d12-9406-936b2e3a373f/download/mnt2015arrondissementahuntsic-cartierville.zip   # Source XML File(s)

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_7)
- GML_1: GML from $(SourceDataset_GML)
- GML_6: GML from $(SourceDataset_GML_19)
- GML_9: GML from $(SourceDataset_GML_16)
- GML_11: GML from $(SourceDataset_GML_20)
- GML_2: GML from $(SourceDataset_GML_12)
- GML_3: GML from $(SourceDataset_GML_8)
- GML_4: GML from $(SourceDataset_GML_7)
- XML_1: XML from $(SourceDataset_XML)

Junction_2
    -> Intersector
Junction_3
    -> Intersector
PenteValeur_existante: Logger
    LOG_FEATURE = LOG_ONLY
    MAXCOORDS = 20
    MAXFEATS = 20
    MESSAGE = Feature is:
    SEVERITY = INFO
    LOGGED -> Tester_2

Bookmark: Lire |Affection du sol
affectationpu (reader SHAPEFILE_1)
    attributes: categorie varchar(60)
    -> Reprojector

Bookmark: Reprojection 3857
Reprojector
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeCreator

Bookmark: Création d'un attribut surface
AttributeCreator
    ATTR_TABLE = SET_TO Aire (varchar(200)) = @Area()
    -> Tester

Bookmark: Filtre en fonction de l'occupation du sol
Tester
    BOOL_OP = OR
    TEST_CLAUSE:
      TEST @Value(categorie) = emplois
      TEST @Value(categorie) = residentiel
      TEST @Value(categorie) = religieux
      TEST @Value(categorie) = mixte
      TEST @Value(categorie) = infrastructure
      TEST @Value(categorie) = institution
    TEST_MODE = TEST
    PASSED -> Tester_Passed
    FAILED -> Tester_Failed

Bookmark: Occupation impermeable
Tester_Passed: Logger
    LOG_FEATURE = LOG_ONLY
    MAXCOORDS = 20
    MAXFEATS = 20
    MESSAGE = Feature is:
    SEVERITY = INFO
    LOGGED -> FeatureWriter [Logged]
    LOGGED -> Junction

Bookmark: POSTGIS_Impermeable
FeatureWriter
    DATASET = geo7630h
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = geo7630h
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written

Bookmark: Hydrographie
Junction
    -> Intersector
Dissolver_Area: Logger
    LOG_FEATURE = LOG_ONLY
    MAXCOORDS = 20
    MAXFEATS = 20
    MESSAGE = Feature is:
    SEVERITY = INFO
    LOGGED -> AttributeManager
Dissolver_Remnants: Inspector

Bookmark: occupation permeable
Tester_Failed: Logger
    LOG_FEATURE = LOG_ONLY
    MAXCOORDS = 20
    MAXFEATS = 20
    MESSAGE = Feature is:
    SEVERITY = INFO

Bookmark: Hydrographie_montreal
CARTO_DRA_EAU_JOUR (reader SHAPEFILE_2)
    attributes: ID number(11,0), TOPONYME varchar(200), EQM varchar(40), SOURCE varchar(30), TRAITEMENT varchar(30), DIFFUSEUR varchar(50), VERSION long
    -> Reprojector_2
PRMHH_CoursEau_Fosses (reader SHAPEFILE_3)
    attributes: NOM varchar(50), type_dv long, cons_cl_dv long, id_ce double, Shape__Len double
    -> Reprojector_2

Bookmark: Reprojection 3857
Reprojector_2
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Bufferer

Bookmark: Zone tampon autour des cours d'eau
Bufferer
    ANGLE = 22.5
    CAP_STYLE_LOOKUP = CAP_ARC
    CORNER_STYLE_LOOKUP = JOIN_ARC
    GROUP_BY = cons_cl_dv DIFFUSEUR EQM fme_feature_type ID id_ce NOM Shape__Len SOURCE TOPONYME TRAITEMENT type_dv VERSION
    MODE = AREA
    OFFSET = 1
    OFFSET_UNITS = KM
    PRECISION = APPROX
    CAP_STYLE = Arc
    CORNER_STYLE = Arc
    BUFFERED -> Dissolver

Bookmark: Regrouper les surfaces
Dissolver
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Dissolver_Area
    REMNANTS -> Dissolver_Remnants

Bookmark: Gestion des attributs
AttributeManager
    ATTR_TABLE:
      REMOVE SOURCE (varchar(30))
      REMOVE DIFFUSEUR (varchar(50))
      REMOVE VERSION (int32)
      REMOVE NOM (varchar(50))
      REMOVE type_dv (int32)
      REMOVE cons_cl_dv (int32)
      REMOVE id_ce (real64)
      REMOVE Shape__Len (real64)
    -> FeatureWriter_2 [Output]
    -> Junction_2

Bookmark: Hydrographie_buffer
FeatureWriter_2
    DATASET = geo7630h
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = geo7630h
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written

Bookmark: MNT (Format GML)
TINRelief (reader GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner
TINRelief (reader GML_6)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner
TINRelief (reader GML_9)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner
TINRelief (reader GML_11)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner
TINRelief (reader GML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner
TINRelief (reader GML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner
TINRelief (reader GML_4)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail xml_buffer
    -> PointCloudCombiner

Bookmark: Creation d'un nuage des points
PointCloudCombiner
    ACCUM_ATTRS = yes
    EXTRACT_RASTER_NODATA = no
    SPACING = 1.0
    ACCUM_ATTRS_NAME = Yes
    EXTRACT_RASTER_NODATA_NAME = No
    -> PointCloudThinner

Bookmark: Reduire la taille
PointCloudThinner
    INTERVAL = 20
    THINNED -> EsriReprojector

Bookmark: Reprojection
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_CSRS_To_WGS_1984
    INTERPOLATION_TYPE = ,NearestNeighbor
    RASTER_CELL_SIZE_LOOKUP = ,PreserveCells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    INTERPOLATION_TYPE_NAME = Nearest Neighbor
    RASTER_CELL_SIZE = Preserve Cells
    REPROJECTED -> PointCloudToPointCoercer

Bookmark: Transformation des nuages des points en couche des vecteurs ponctuels
PointCloudToPointCoercer
    ACCUM_ATTRS = YES
    CONVERT_TO = POINT
    PART_NUMBER_ATTR_NAME = _part_number
    POINT_COMPONENTS = z
    POINT_COMPONENTS_PRESERVE_TYPE = ATTRIBUTES
    ACCUM_ATTRS_NAME = Yes
    CONVERT_TO_DISPLAY = Individual Points
    POINT_COMPONENTS_PRESERVE_DISPLAY = Attributes
    COERCED -> SurfaceModeller [POINTS/LINES]

Bookmark: generons le DEM_Raster
SurfaceModeller
    ADDZ = NO
    BREAKLINE_METHOD = Yes
    CONFORMING_TOLERANCE_LOOKUP = AUTO
    CONTOUR_INTERVAL = 20
    DRAPE_TYPE = VERTEX
    INTERPOLATION_TYPE = AUTO
    NODATA_VALUE = 9999
    TOLERANCE = 2
    X_SPACING = 30
    Y_SPACING = 30
    ADDZ_TYPE = Replace Z
    CONFORMING_TOLERANCE = Automatic
    DEMRaster -> FeatureWriter_3 [DEMRaster]
    DEMRaster -> RasterPropertyExtractor

Bookmark: Extraire les metadonnée du Raster
RasterPropertyExtractor
    -> RasterBandNodataRemover

Bookmark: Supression des valeurs nulles
RasterBandNodataRemover
    -> RasterSlopeCalculator

Bookmark: Calcul de la pente
RasterSlopeCalculator
    ALGORITHM_LOOKUP = Horn
    INTERPOLATE_NODATA_LOOKUP = InterpolateNodata
    OUTPUT_TYPE_LOOKUP = Degrees
    ALGORITHM = Horn
    INTERPOLATE_NODATA = Yes
    OUTPUT_TYPE = Degrees
    -> RasterExpressionEvaluator [A]

Bookmark: Classification des pentes
RasterExpressionEvaluator
    EXPRESSION_LIST:
      INT64 IF (A[0] <= 5, 1,
         IF ( A[0] <= 15, 2,
            IF ( A[0] <= 30, 3,
               IF ( A[0]  <= 45, 4, 5))))
    MODE = One Raster
    RESULT -> RasterToPolygonCoercer

Bookmark: Raster vers polygône
RasterToPolygonCoercer
    EXTRACT_NODATA = No
    LABEL_ATTRIBUTE = pente
    PRESERVE_ATTRIBUTES_LOOKUP = YES
    EXTRACT_NODATA_LOOKUP = No
    PRESERVE_ATTRIBUTES = Yes
    POLYGONS -> AttributeManager_2

Bookmark: Gestion des attributs
AttributeManager_2
    ATTR_TABLE:
      REMOVE _num_rows (uint32)
      REMOVE _num_columns (uint32)
      REMOVE _spacing_x (real64)
      REMOVE _spacing_y (real64)
      REMOVE _origin_x (real64)
      REMOVE _origin_y (real64)
      REMOVE _rotation_x (real64)
      REMOVE _rotation_y (real64)
      REMOVE _min_x (real64)
      REMOVE _min_y (real64)
      REMOVE _max_x (real64)
      REMOVE _max_y (real64)
      REMOVE _cell_origin_x (real64)
      REMOVE _cell_origin_y (real64)
      REMOVE _upper_left_x (real64)
      REMOVE _upper_left_y (real64)
      REMOVE _upper_right_x (real64)
      REMOVE _upper_right_y (real64)
      REMOVE _lower_right_x (real64)
      REMOVE _lower_right_y (real64)
      REMOVE _lower_left_x (real64)
      REMOVE _lower_left_y (real64)
    -> AreaBuilder

Bookmark: Creation des surface
AreaBuilder
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = YES
    DROP_HOLES = No
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> Dissolver_3

Bookmark: regroupons les surface
Dissolver_3
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Generalizer

Bookmark: lisser les polygônes
Generalizer
    ALG = McMaster
    DISPLACEMENT = 50.0
    NUMNEIGHBORS = 2
    PRESERVE = No
    PRESERVE_PATHS_LOOKUP = NO
    ALG_TEXT = McMaster (Smooth)
    PRESERVE_PATHS = No
    -> FeatureWriter_4 [Output]
    -> Junction_3

Bookmark: Intersection de 3 couches
Intersector
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> AttributeManager_3

Bookmark: Gestions des attributs
AttributeManager_3
    ATTR_TABLE:
      REMOVE Aire (varchar(200))
      REMOVE categorie (varchar(60))
      REMOVE ID (number(11,0))
      REMOVE TOPONYME (varchar(200))
      REMOVE EQM (varchar(40))
      REMOVE TRAITEMENT (varchar(30))
      REMOVE fme_basename (buffer)
      REMOVE _overlaps (uint32)
    -> AttributeFilter_2

Bookmark: Eliminons les valeurs manquantes
AttributeFilter_2
    ATTR_NAME = pente
    ATTR_VALUES = <Empty>,<Missing>,<Null>,<Unfiltered>
    <UNFILTERED> -> PenteValeur_existante

Bookmark: Filtrer les pentes
Tester_2
    BOOL_OP = OR
    TEST_CLAUSE:
      TEST @Value(pente) = 1
      TEST @Value(pente) = 2
    TEST_MODE = TEST
    PASSED -> AreaBuilder_2

Bookmark: Creation de surface
AreaBuilder_2
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = Yes
    DROP_HOLES = No
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> GeometryValidator

Bookmark: Validation de la geometrie
GeometryValidator
    ISSUE_ATTR_NAME = _issues
    PRESETS = Custom
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION
    SUMMARY = Detailed
    PASSED -> FeatureWriter_5 [Passed]

Bookmark: Importation POSTGIS
FeatureWriter_5
    DATASET = geo7630h
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = geo7630h
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written

Bookmark: MNT_Polygone_POSGIS
FeatureWriter_4
    DATASET = geo7630h
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = geo7630h
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written

Bookmark: MNT_POSTGIS_RASTER
FeatureWriter_3
    DATASET = geo7630h
    DATASET_ATTR = _dataset
    FEATURE_TYPE_LIST_ATTR = _feature_types
    FORMAT = POSTGIS_RASTER
    POSTGIS_RASTER_BULK_COPY = YES
    POSTGIS_RASTER_COORDINATE_SYSTEM_GRANULARITY = FEATURE_TYPE
    POSTGIS_RASTER_LOWERCASE_ATTRIBUTE_NAMES = Yes
    POSTGIS_RASTER_NAMED_CONNECTION = geo7630h
    POSTGIS_RASTER_SPATIAL_COLUMN_NAME = rast
    POSTGIS_RASTER_START_TRANSACTION = 0
    POSTGIS_RASTER_STRICT_TEMPORAL_TYPE_HANDLING = Yes
    POSTGIS_RASTER_TRANSACTION_INTERVAL = 100
    TOTAL_FEATURES_WRITTEN_ATTR = _total_features_written
